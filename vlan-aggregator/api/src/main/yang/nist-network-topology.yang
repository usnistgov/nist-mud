module nist-network-topology {
  yang-version 1.1;
  namespace "urn:nist:params:xml:ns:yang:nist-network-topology";
  prefix network-topology;

  import ietf-inet-types {
    prefix inet;
  }
  
  organization
    "NIST Advanced Networking Technologies Division.";

  contact
    "Web: http://www.nist.gov
    email: mranga@nist.gov
    ";
  description
    "Description of the topology of the system. 
     This identifies the npe and cpe devices associated
     with those NPE devices.";

  revision 2017-09-15 {
    description
      "Experimental.";
    reference
      "Vlan tag manager";
  }

  grouping trunks {
      description
          "Trunk port configuration";
      list forwarders {
        leaf switch-id {
            description 
               "the NPE switch identifier, eg: openflow:2 ";
            type inet:uri;
            mandatory true;
        }
     
        leaf trunk-interface {
            description
             "The physical interface for the trunk port eg. 2:s2-eth1";
            type string;
            mandatory true;
        }

        leaf-list  vlans {
            description
             "The vlan tags to be sent to this trunk port. This is an array of integers. Empty list is treated as a wildcard.";
            type int32;
        }
     }
  }

  grouping links {
      description
          "A list of links";

      list link {

        leaf descriptive-name {
            description 
                "Descriptive name for this link";
            type string;
        }
        
        leaf uplink-interface {
            description
             "The physical interface for the uplink port";
            type string;
            mandatory true;
        }
        
        leaf vlan {
            description
             "The vlan tags to be attached to outbound packets. We will use this
              Vlan tag to configure a vnf on openstack.";
            type int32;
            mandatory true;
        }

        leaf cpe-switch {
          description 
             "ID of CPE switch associated with this NPE switch.";
          type inet:uri;
          mandatory true;
        }

        leaf openstack-stack-name {
          description 
            "stack name associated with this CPE -- all parameters are drawn from there except for the VLAN ID.";
          type string;
          mandatory false;
        }
      }
  }

  container topology {
      description
          "Network topology gives an association between npe switches and 
          sets of CPE switches";
      uses links;
  }

  container trunk-switches  {
      description
          "Trunk switches that route packets to the CPE cloud and CPE links that connect to the cloud.";
      uses trunks;
  }

}
