module ietf-mud-reporter {
  yang-version 1.1;
  namespace "urn:ietf:params:xml:ns:yang:ietf-mud-reporter";
  prefix mud-reporter;

  import ietf-inet-types {
    prefix inet;
  }
  import ietf-yang-types {
    prefix yang;
  }

  organization
    "IETF OPSAWG (Ops Area) Working Group";
  contact
    "WG Web: http://tools.ietf.org/wg/opsawg/
     WG List: opsawg@ietf.org
     Author: Eliot Lear
     lear@cisco.com
    ";
  description

    "This YANG module specifies the reporting format for MUD managers
     to use when they are reporting to manufacturers.

     Copyright (c) 2019 IETF Trust and the persons identified as
     authors of the code.  All rights reserved.

     Redistribution and use in source and binary forms, with or
     without modification, is permitted pursuant to, and subject to

     the license terms contained in, the Simplified BSD License set
     forth in Section 4.c of the IETF Trust's Legal Provisions
     Relating to IETF Documents
       (https://trustee.ietf.org/license-info).

     This version of this YANG module is part of RFC XXXX
     (https://www.rfc-editor.org/info/rfcXXXX); see the RFC itself
      for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
    ";

  revision 2019-06-21 {
    description
      "Initial proposed standard.";
    reference
      "RFC XXXX: Extension for MUD Reporting";
  }

  container mud-reporter {
    uses mud-reporter-grouping;
    description "Reporter Information.";
  }

  grouping mud-reporter-grouping   {

    description
      "MUD reporter container.";
    leaf mudurl {
      type inet:uri;
      description
        "The MUD-URL for which the report is being sent.";
    }
    list mud-report {
      key "time";
      description
        "individual records.";

      leaf enforcement-point-id {
        type string;
        description
           "Identifying information for the enforcement-point
            (e.g. switch) that is making this report. This is
            an opaque identifier. ";

      }

      leaf time {
        type yang:timestamp;
        description
          "when this happened.";
      }


      leaf mycontrollers {
        type uint32;
        description
          "how many entries for my-controller.";
      }

      list controllers {
        key "uri";
        description
          "list of controllers and how many there were.";
        leaf uri {
          type inet:uri;
          description
            "the class URI of this controller";

        }
        leaf count {
          type uint32;
          description
            "number of devices serving this class.";
        }
      }

      leaf samemanufacturers {
        type uint32;
        description
          "number of devices matching same
           manufacturer.";
      }



      list models {
        key "uri";

        description
          "List of models and how many there were.";
        leaf uri {
          type inet:uri;

          description
            "the URI of this model";
        }
        leaf count {
          type uint32;
          description
            "number of devices serving this class.";

        }
      }

      list manufacturers {
        key "authority";

        description
          "List of models and how many there were.";
        leaf authority {
          type string;
          description
            "the URI of this model";

        }
        leaf count {
          type uint32;
          description
            "number of devices serving this class.";

        }
      }

      list domains {
        key "hostname";
        description
          "list of hosts, and ip addresses if known.";

        leaf hostname {
          type string;
          description
            "the host listed";
        }

        leaf-list ip-addresses {
          type inet:ip-address;
          description
            "ipv4 or v6 address mapping for this host if
             known.";
        }
      }

      leaf-list opaque-identifier {
          type string;
          description
            "List of opaque identifiers
             for the devices generating this report. ";

      }

      list drop-counts {
         description
            "List of packet counts for dropped packets 
             and the reason why they were dropped";
         uses drop-count;
      }

      list match-counts {
         description
            "List of packet counts for packets that were 
             not dropped.";
        uses pass-count;
      }
    }

  }


  grouping pass-count {
    description
     "Count of packets for each passing MUD ACE. in the MUD file.
      The ACE's are named with the <name of the ACL> / <name of ACE>";
    leaf ace-name {
      type string;
      description
             "Name of ACE";
    }

    leaf packet-count {
      type uint64;
      description
       "Pass count (count of number of packets that matched
        this ACE and made it through";
    }
  }

  grouping drop-count {
    description
      "Violating packet related to this MUD file are classfied.";
    leaf reason {
        type enumeration {
            enum nomatch {
               description 
               "No matching mud rule was found";
            }
            enum connection-block {
                  description 
                  "Connection was blocked";
           }
       }
    }
    choice drop-reason {
      description
        "Reason for packet being dropped";
      case nomatch {
          description
           "No mud rule matched";
      }
      case tcp-blocked {
        leaf ace-name {
          type string;
          description
            "ACE name for the MUD ACE that specified the direction of initiation.
            TCP connection initiated in the wrong direction.";
          }
       }
     }
     leaf direction {
        type enumeration {
          enum to-device {
            description
              "Packet was traveling toward the device";
          }
          enum from-device {
            description
              "Packet was traveling away from the device";
          }
        }
        description
          "which way packet is going";
     }

    leaf drop-count {
      type uint64;
      description
        "Measure of dropped packets for this classification.";
    }
  }
}
