module sdnmud {
    yang-version 1.1;
    namespace "urn:opendaylight:params:xml:ns:yang:sdnmud";
    prefix "sdnmud";

  import ietf-inet-types {
    prefix inet;
  }
  import ietf-yang-types {
    prefix yang;
  }

  import ietf-mud-reporter {
    prefix mr;
  }
  
  organization
    "NIST Advanced Networking Technologies Division.";

  contact
    "Web: http://www.nist.gov
    email: mranga@nist.gov
    ";
  description
    "Application system configuration parameters. ";

  revision 2017-09-15 {
    description
      "Implementation YANG model for system configuration. This provides various parameter 
       settings for the application.";
  }



  container sdnmud-config {

      leaf ca-certs {
            type string;
            default "lib/security/cacerts";
            description
                "Certification authority (CA) certificates for verifying MUD profile.";
      }


      leaf key-pass {
            type string;
            default "changeit";
            description
                "Key store password.";
      }

      leaf table-start {
            type uint32;
            default "0";
            description
                "Start of tables in rules table space.";
      }

      leaf broadcast-rule-table {
            type uint32;
            default "4";
            description
                "Table location for the Broadcast rule.";
      }

      leaf drop-rule-table {
            type uint32;
            default "5";
            description 
               "Table location for the Packet Drop rule"; 
      }

      leaf mfg-id-rule-cache-timeout {
            type uint32;
            default "60";
            description
                "Time (in seconds) for timeout of flow rule that classifies packets by manufacturer.";
      }

      leaf trust-self-signed-cert {
           type boolean;
           default "true";
           description
                "Whether or not to trust Certs that are self signed. This is for DEBUGGING ONLY 
                self signed Certs should not be trusted under normal circumstances";
      }

      leaf strict-hostname-verify {
           type boolean;
           default "false";
           description
                "Whether or not to do Hostname verification when connecting to the 
                mudfile (manufacturer) server. For debugging puroses only";
      }

      leaf relaxed-acl {
           type boolean;
           default "true";
           description
              "Fowrard packet before installing classification rules - this reduces the packet drop and allows
               for continued operation when controller is not connected. Warn operator if ACL violated.";
      }

      leaf block-mac-on-mud-profile-failure {
           type boolean;
           default "true";
           description
                "Block the mac address if the mud file does not install 
                (i.e. on signature verification failure or failure to fetch the mud profile)";
      }

      leaf reporter-frequency {
            type uint32;
            description 
               "How often to send mud-reporter reports (seconds).";

      }

  }


  rpc clear-packet-count {
    output {
        leaf success {
            description 
                "Clear the packet count. This is for testing purposes. Return OK if the call succeeded. 
                 This is for test and measurement purposes.
                ";
            type boolean;
        }
    }
  }

  rpc clear-cache {
    output {
        leaf success {
            description 
                "Clear the mfg model flow rules in tables 3 and 4. This is for test and measurement purposes. 
                 Return OK if the call succeeded. ";
            type boolean;
        }
    }
  }

  rpc get-packet-count {
    output {
        leaf packet-count {
            description 
                "returns the number of packets seen at the controller. 
                This is for performance benchmarking.";
            type uint32;
        }

        leaf mud-packet-count {
            description 
                "returns the number of packets seen at the controller resulting from packets directed to the 
                 controller from flow rules in tables 3,4,5. This is for performance benchmarking.";
            type uint32;
        }
    }
  }

  rpc get-mud-unmapped-addresses {
    output {
      leaf-list unmapped-device-addresses {
            description
                "returns a list of unmanaged devices - i.e. MAC addresses that do not have MUD profiles";
      type string;
    }
   }
  }

  rpc clear-mud-rules {
    output {
        leaf success {
            description 
                "Clear the mud rules table. This is for testing purposes. Return OK if the call succeeded. 
                 This is for test and measurement purposes.
                ";
            type boolean;
        }
    }
  }


    rpc get-quarantine-macs {
        description
            "get the list of mac addresses that are quarantined";
        output {
           leaf-list mac-addresses {
              description
                "The list of mac address that are quarantined";
                type yang:mac-address;
            }
        }
    }

    rpc unquarantine {
       description
           "Remove the given MAC address from the quarantine database";
       input {
             leaf device-mac-address {
                description 
                 "The quearantine mac to delete";
              type yang:mac-address;
            }
        }
    }

    rpc unquarantine-all {
        description
            "Remove all mac addresses from the quarantine database";

    }

    rpc quarantine {
       description
            "Add the given MAC address to the quarantine database";
       input {
           leaf device-mac-address {
              description 
                 "The MAC address to quarantine";
              type yang:mac-address;
            }
        }
    }

  rpc add-controller-mapping {
     description
        "Resolve a controller to a list of addresses";
     input {
        leaf switch-id {
            description
              "The URI of the switch / enforcement point.";
            type string;
        }

        leaf controller-uri {
            description
              "The controller URI";
            type inet:uri;
        }

       

        leaf-list address-list {
            description
               "The list of IP addresses associated with the controller URI";
            type inet:ipv4-address;
        }
     }
  }


  rpc get-mud-metadata-mapping {
    description
         "Get the Metadata mapping in human readable form given a HEX input";
    input {
        leaf metadata-and-mask {
            description 
                "The HEX metadata and mask to resolve (use slash as separator use 0x to indicate hex).
                 Just dump the flow rules in ovs and supply the metaata as a parameter. This is for debugging.";
            type string;
            mandatory true;
        }
    }

    output {
            leaf masked-metadata {
               description 
                "The HEX masked metdata";
                type string;
            }
            leaf src-manufacturer {
                description
                        "Src Manufacturer url";
                type string;
            }
            leaf src-model {
                description
                       "Src Model";
                type inet:uri;
            }
            leaf src-local-networks-flag {
                type boolean;
                description 
                     "Local networks flag";
            }
            leaf src-quarantine-flag {
                description 
                     "Qurarantene flag networks match";
                type boolean;
            }
            leaf src-mac-blocked-flag {
                description 
                     "src mac blocked flag";
                type boolean;
            }
            leaf dst-model {
                description
                       "Dst Model";
                type inet:uri;
            }
            leaf dst-manufacturer {
                description 
                       "Dst Manufacturer";
                type string;
            }
            leaf dst-local-networks-flag {
                description 
                     "Local networks flag";
                type boolean;
            }
            leaf dst-quarantine-flag {
                description 
                     "Qurarantene flag networks match";
                type boolean;
            }
            leaf dst-mac-blocked-flag {
                description 
                     "dst mac blocked flag";
                type boolean;
            }

    }

  }

rpc get-src-mac-classification {
    description
        "Get the classification label for src mac in human readable form.";

    input {
        leaf mac-address {
           description 
               "Src Mac address";
           type yang:mac-address;
        }
    }

    output {

            leaf metadata {
               description
                    "The metadata as a hex string";
                type string;
            }

            leaf src-manufacturer {
                description
                        "Src Manufacturer url";
                type string;
            }
            leaf src-model {
                description
                       "Src Model";
                type inet:uri;
            }
            leaf src-local-networks-flag {
                type boolean;
                description 
                     "Local networks flag";
            }
            leaf src-quarantine-flag {
                description 
                     "Qurarantene flag networks match";
                type boolean;
            }

            leaf src-blocked-flag {
                description 
                     "Blocked due to mud profile failure";
                type boolean;
            }

    }

}

rpc get-dst-mac-classification {
    description
        "Get the classification label for dst mac in human readable form.";

    input {
        leaf mac-address {
           description 
               "Src Mac address";
           type yang:mac-address;
        }
    }

    output {
            leaf metadata {
               description
                    "The metadata as a hex string";
                type string;
            }

            leaf dst-manufacturer {
                description
                        "Src Manufacturer url";
                type string;
            }
            leaf dst-model {
                description
                       "Src Model";
                type inet:uri;
            }
            leaf dst-local-networks-flag {
                type boolean;
                description 
                     "Local networks flag";
            }
            leaf dst-quarantine-flag {
                description 
                     "Qurarantene flag networks match";
                type boolean;
            }
            leaf dst-blocked-flag {
                description 
                     "Blocked due to MUD profile failure";
                type boolean;
            }

    }

}



  rpc get-flow-rules {

     description
        "Get the MUD flow rules from the given switch ID for to the 
         given MUD URL";

     input {

          leaf mud-url {
             description 
                "The MUD URL of interest";
             type inet:uri;
           }

           leaf switch-id {
              description
                    "The Switch ID eg. openflow:123";
              type inet:uri;
           }

       }

       output {

          list flow-rule {

            description
                "Human readable flow rules";

            leaf masked-metadata-match {
               description 
                "The raw HEX masked metdata to match on";
                type string;
            }

            leaf src-manufacturer {
                description
                       "Src Manufacturer url";
                type string;
            }

            leaf src-model {
                description
                       "Src Model";
                type inet:uri;
            }

            leaf dst-model {
                description
                       "Dst Model";
                type inet:uri;
            }

            leaf dst-manufacturer {
                description 
                       "Dst Manufacturer";
                type string;
            }

            leaf src-local-networks-flag {
                type boolean;
                description 
                     "Local networks flag";
            }

            leaf dst-local-networks-flag {
                description 
                     "Local networks flag";
                type boolean;
            }

            leaf src-quarantine-flag {
                description 
                     "Qurarantene flag networks match";
                type boolean;
            }

            leaf src-mac-blocked-flag {
                description 
                     "Src MAC blocked flag";
                type boolean;
            }

            leaf dst-quarantine-flag {
                description 
                     "Qurarantene flag networks match";
                type boolean;
            }

            leaf dst-mac-blocked-flag {
                description 
                     "Dst MAC blocked flag";
                type boolean;
            }

            leaf priority {
                description 
                    "Priority";
                type uint32;
            }

            leaf flow-id {
                description 
                    "Flow ID";
                type string;
            }

            leaf flow-name {
                 description
                     "Flow descriptive name";
                 type string;
            }
    
            leaf table-id {
                description
                    "The table ID";
                type uint32;
            }

            leaf flow-rule {
                description
                    "The formated flow rule";
                type string;
            }

            leaf packet-count {
                description
                    "The packet count";
                type uint64;
            }

            leaf byte-count {
                description
                    "The byte count";
                type uint64;
            }
         }
       }
   }

   rpc get-mud-reports {
      input {
        leaf mud-url {
	    description
               "The mud uri for which to deliver the report";
        type inet:uri;
       }
      }

      output {
         container report {
           description "MUD report";
           uses mr:mud-reporter-grouping;
         }
      }
   }

   rpc add-controller-wait-input {
      input {
        leaf mud-url {
	        description
               "The mud uri for which to wait till ready";
            type inet:uri;
        }
      }

      output {
         container report {
            description "Success or failure. If the device does not exist then failure.";
            leaf success-flag {
                description "MUD report. This could be success if the device exists or failure";
                type boolean;
            }
         }
      }
   }

   rpc get-mud-urls {
      input {
        leaf-list mud-url {
	        description
               "The mud uri for which to wait till ready";
            type string;
        }
      }

      output {
         container report {
            description "Return true with a URL of any missing MUD urls.";
            leaf mud-url {
                description "MUD URL that are present and missing in the input. ";
                type string;
            }
         }
      }
   }

}
