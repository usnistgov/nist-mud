module nist-mud-device-association {
  yang-version 1.1;
  namespace "urn:nist:params:xml:ns:yang:nist-mud-device-association";
  prefix mud-device-association;

  import ietf-inet-types {
    prefix inet;
  }

  import ietf-yang-types {
    prefix yang;
  }


  organization
    "NIST Advanced Networking Technologies Division.";

  contact
    "Web: http://www.nist.gov
    email: mranga@nist.gov
    ";
  description
    "A correlation between Device Identifier and MUD URL.
     A way of telling the controller to apply a given set of MUD
     rules to a given device.";

  revision 2017-09-15 {
    description
      "Initial proposed standard.";
    reference
      "RFC XXXX: Manufacturer Usage Description
       Specification";
  }

  grouping device-mapping  {
    description 
        "A mapping of device ID to mud URL";

     leaf-list device-id {
      	description
           "IOT device identifier list to be associated with this MUR URI. (MAC address)";
        type  yang:mac-address;
     }

     leaf mud-url {
      	description
           "MUD uri to associate with this device";
        type inet:uri;
        mandatory true;
     }
  
  }

  
  container mapping {
     description
         "Mapping between device ID and MUD URI.
          This can be posted from an external agent
          or the administrator interface.";
    uses device-mapping;
  }

  container mappings {
     list mapping {
       leaf-list device-id {
      	 description
           "IOT device identifier list to be associated with this MUR URI. (MAC address)";
          type  yang:mac-address;
       }

       leaf mud-url {
      	 description
           "MUD uri to associate with this device";
         type inet:uri;
         mandatory true;
     }
   }
}



  container quarantine-device {
      description
        "List of MAC addresses of devices under
         quarantene";
      leaf-list qurantine-mac {
          type yang:mac-address;
          description
            "Mac address of device marked as quarantene";
      }
  }



  notification mapping-notification {
       description
           "Publish that a MAC to MUD mapping was changed. 
            This is for other services to be notified. A notification
            is sent out when the mapping changes.";
        container mapping-info {
           description
              "The mapping for the device (MUD URI and MAC address) ";
            list mapping-info-list {
                uses device-mapping;
            }
        }
  }

  notification ace-violation-notification {
       description
        "Publish that a device violated its allowable behavior, 
        The container puts out notifications that a violation has 
        been observed. The policy application needs to set the state
        take any necessary action to get the device out of quarantene.
        It can do this by issuing an API request to the controller which
        will then mark the device as being out of quarantene.";
       container ace-violation-info {
          description 
                "The device identification for the misbehaving device";
          leaf mac-address {
             description
               "The device MAC address";
             type yang:mac-address;
          }
    
          leaf mud-url {
             description
               "The MUD url for the device";
             type inet:uri;
          }
           
       }
  }
}
