module nist-mud-controllerclass-mapping {
  yang-version 1.1;
  namespace "urn:nist:params:xml:ns:yang:nist-mud-controllerclass-mapping";
  prefix class-mapping;

  import ietf-inet-types {
    prefix inet;
  }

  import ietf-yang-types {
    prefix yang;
  }


  organization
    "National Institute of Standards and Technlogoy (NIST)";
  contact
    "http://www.nist.gov/
     mranga@nist.gov
    ";
  description
    "Class URI and list of ipv4 addresses";

  revision 2017-09-15 {
    description
      "Implementation YANG model";
    reference
      "RFC XXXX: Manufacturer Usage Description
       Specification";
  }




  
    grouping controller-map {
        leaf uri {
            description
              "The controller URI";
            type inet:uri;
        }

        leaf-list address-list {
            description
               "The list of IP addresses associated with the controller URI";
            type inet:ipv4-address;
        }

     }


  container controllerclass-mapping {
     description
         "Local network configuration. This is scoped on a per-switch basis. If a switch 
          does not have a mapping, then no MUD rules will be applied for the switch.";

     leaf switch-id {
        description
            "URI of the CPE switch for which to apply this controller class mapping.
            This is normally of the form openflow:switchId where switchId is often the
            MAC address of the switch.";
        type inet:uri;
        mandatory true;
     }


     list controller {
        description
            "The URI for the controller followed by a list of addresses.";
        uses controller-map;
     }

     leaf-list local-networks {
       description
          "Network address prefix for local networks.";
       type string; 
    }
    
    leaf-list local-networks-excluded-hosts {
       description
          "Network IP address that are excluded from the local networks classification. 
          Typically these are local network services such as routers.";
       type string; 
    }


    leaf wireless {
       description
          "Flag indicating whether the switch is wireless or not";
       type boolean;
       default false;
    }

  }


}
