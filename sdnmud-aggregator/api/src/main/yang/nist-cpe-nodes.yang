module nist-cpe-nodes {
  yang-version 1.1;
  namespace "urn:nist:params:xml:ns:yang:nist-cpe-nodes";
  prefix mud-nodes;

  import ietf-inet-types {
    prefix inet;
  }
  
  organization
    "NIST Advanced Networking Technologies Division.";

  contact
    "Web: http://www.nist.gov
    email: mranga@nist.gov
    ";
  description
    " This identifies the collection of switches where MUD rules are installed
      (i.e. the collection of switches (such as openflow:xxx) which are managed by this
      application.";

  revision 2017-09-15 {
    description
      "Implementation YANG model.";
    reference
      "Collection of CPE nodes where MUD-related flows are installed.";
  }

  container cpe-collections {
      description
          "The collection of CPE switches on which MUD rules are installed.";
       leaf-list cpe-switches {
          description 
             "CPE switch ID's where MUD rules are installed. These are of the form openflow:xxxx where xxxx is usually the MAC address of the switch in HEX";
          type inet:uri;
       }
  }
}
