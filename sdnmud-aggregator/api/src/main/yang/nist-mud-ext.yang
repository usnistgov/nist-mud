module nist-local-policy {
  yang-version 1.1;
  namespace "urn:ietf:params:xml:ns:yang:nist-mud-ext";
  prefix nist-mud;

  import ietf-mud {
    prefix ietf-mud;
  }

  import ietf-inet-types {
    prefix inet;
  }

  organization
    "NIST";
  contact
    "mranga@nist.gov";

  description
      "Experimental MUD extensions";

  revision 2019-04-28 {
    description
      "Softer handling of MUD ACEs";
  }

  typedef error-handling {
    type enumeration {
      enum inform {
         description
            "inform manufacturer but don't drop the packet";
       }

       enum drop {
         description
            "drop packet on violation";
       }

       enum inform-and-drop {
         description
            "inform manufacturer and drop packet on violation";
       }

       enum quarentene  {
          description
            "Quarantene device - can only access update site on access violation. 
             No other interactions are permitted.";
       }
     }
  }

  grouping error-handling-grouping {
      leaf mud-url {
        type inet:uri;
        description
            "The mud URI for which to implement this drop policy";
      }
   
      leaf update-host {
        type string;
        description
            "The host (from where updates are pushed)";
      }

      leaf update-port {
        type int32;
        description
            "The port (from where updates are pushed)";

      }
      
      leaf access-violation-policy {
        type error-handling;
        description
            "what to do when mud policy is violated";
      }
  }
  
}
