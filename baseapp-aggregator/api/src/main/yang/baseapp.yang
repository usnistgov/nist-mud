module baseapp {
    yang-version 1.1;
    namespace "urn:opendaylight:params:xml:ns:yang:baseapp";
    prefix "baseapp";

    organization
    "NIST Advanced Networking Technologies Division.";

  contact
    "Web: http://www.nist.gov
    email: mranga@nist.gov
    ";
  description
    "Application system configuration parameters. ";

  revision 2017-09-15 {
    description
      "Implementation YANG model for system configuration. This provides various parameter
       settings for the application.";
  }

  container baseapp-config {
    leaf normal-rule-table {
        description 
            "The table location for the normal rule";
        type uint32;
        default "0";
    }
    leaf wireless-switch {
        description
            "A flag indicating whether or not the switch is a wireless SDN switch";
        type boolean;
        default "false";
    }
  }
}
