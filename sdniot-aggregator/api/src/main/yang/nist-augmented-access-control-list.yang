module nist-mud-acl {
  yang-version 1.1;
  namespace "urn:nist:params:xml:ns:yang:nist-mud-acl";
  prefix nist-acl;

  import ietf-access-control-list  {
    prefix acl;  
  }

  import ietf-yang-types {
    prefix yang;
  }

  import ietf-inet-types {
    prefix inet;
  }

  augment "/acl:access-lists" {
     container mud-info {
        leaf mud-uri {
            type inet:uri;
        }
     }
  }

}
