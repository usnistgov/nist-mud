module nist-ids-registration {
  yang-version 1.1;
  namespace "urn:nist:params:xml:ns:yang:nist-ids-registration";
  prefix nist-ids;

  import ietf-yang-types {
    prefix yang;
  }

  import ietf-inet-types {
    prefix inet;
  }


  revision 2017-09-15 {
    description
      "Implementation class.";
    reference
      "RFC XXXX: Manufacturer Usage Description
       Specification";
  }

  organization
    "NIST Advanced Networking Technologies Division.";

  contact
    "Web: http://www.nist.gov
    email: mranga@nist.gov
    ";

  rpc ids-registration {
    input {


        leaf-list flow-spec {
            description
                "The flows of interest. These identify the flows of interest. e.g. 
                 flow:toaster.nist.gov:local means all the local flows from manufacturer toaster.nist.gov
                      to go to the IDS.
                 flow:toaster.nist.gov:remote means IDS wants all the remote flows from devices made by manufacturer 
                    toaster.nist.gov to go to IDS.
                 flow:toaster.nist.gov:drop means  IDS wants access to the flows from devices made by manufacturer
		    toaster.nist.gov that were dropped.
                 flow:NONE:remote means all the remote flows that do not have a MUD profile go to IDS.
                 flow:NONE:local means all the flows that do not have a MUD profile that are local go to IDS.
                 ";
            type inet:uri;
        }

        leaf filter-duration {
           description
               "The duration for which to sample the flow";
           type int32;
           default 30000;
        }

        leaf node-id {
            description
                "The Node ID and port of the switch where IDS will register";
            type inet:uri;
            mandatory true;
         }

        leaf-list  ports {
            description
                "The ports where the switch will get packets";
            type int32;
        }
    }
    
    output {

        leaf return-code {
            description
                "The status code. 0 for success -1 for failed.";
            type int32;
        }

        leaf status-message {
            description 
                "Descriptive error message ";
            type string;
        }
    }

  }
}
