module nist-mud-device-association {
  yang-version 1.1;
  namespace "urn:nist:params:xml:ns:yang:nist-mud-device-association";
  prefix mud-device-association;

  import ietf-inet-types {
    prefix inet;
  }

  import ietf-yang-types {
    prefix yang;
  }


  organization
    "NIST Advanced Networking Technologies Division.";

  contact
    "Web: http://www.nist.gov
    email: mranga@nist.gov
    ";
  description
    "A correlation between Device Identifier and MUD URL.
     A way of telling the controller to apply a given set of MUD
     rules to a given device.";

  revision 2017-09-15 {
    description
      "Initial proposed standard.";
    reference
      "RFC XXXX: Manufacturer Usage Description
       Specification";
  }

  grouping device-mapping  {
    description 
        "A mapping of device ID to mud URL";

     leaf-list device-id {
      	description
           "IOT device identifier list to be associated with this MUR URI. (MAC address)";
        type  yang:mac-address;
     }

     leaf mud-url {
      	description
           "MUD uri to associate with this device";
        type inet:uri;
        mandatory true;
     }
  
  }

  
  container mapping {

     description
         "Mapping between device ID and MUD URI.
          This can be posted from an external agent
          or the administrator interface.";

    uses device-mapping;

  }

  notification mapping-notification {
       description
           "Publish that a MAC to MUD mapping was generated. 
            This is for other services to be notified.";
        leaf manufacturer-id {
            description
               "The global manufacturer ID";
            type uint32;
        }

        leaf model-id {
            description
                "The global model ID";
            type uint32;
        }

        container mapping-info {
           description
              "The mapping for the device (MUD URI and MAC address) ";
            uses device-mapping;
        }
  }

  
}
