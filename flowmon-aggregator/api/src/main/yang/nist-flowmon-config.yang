module nist-flowmon-config {
  yang-version 1.1;
  namespace "urn:nist:params:xml:ns:yang:nist-flowmon-config";
  prefix nist-flowmon;

  import ietf-yang-types {
    prefix yang;
  }

  import ietf-inet-types {
    prefix inet;
  }


  organization
    "National Institute of Standards and Technlogoy (NIST)";

  contact
    "http://www.nist.gov/
     mranga@nist.gov
    ";

  description
    "Flow Monitor configuration. This supplies ODL with the mac address
     and authentication information of the Flow Monitor. When Flow Monitor 
     sends a UDP packet to a specified port with the authenication
     iformation in the payload, the platform can identify the Flow Monitor
     and the port from which it will connect.";

  revision 2017-09-15 {
    description
      "Implementation YANG model";
    reference
      "NIST- Elastic Flow Monitor project.";
  }



   container flowmon-config {
       list flowmon-config-data {
        leaf-list flow-spec {
             description
                    "The flows of interest. These identify the flows of interest. e.g. 
                    flow:toaster.nist.gov:local means all the local flows from manufacturer toaster.nist.gov
                    to go to the Flow Monitor.
                    flow:toaster.nist.gov:remote means Flow Monitor wants all the remote flows from devices made by manufacturer 
                    toaster.nist.gov to go to Flow Monitor.
                    flow:toaster.nist.gov:drop means  Flow Monitor wants access to the flows from devices made by manufacturer
 		            toaster.nist.gov that were dropped.
                    flow:NONE:remote means all the remote flows (leaving the switch) that do not have a MUD profile go to Flow Monitor.
                    flow:NONE:local means all the flows that do not have a MUD profile that are local go to Flow Monitor.
                    ";
           type inet:uri;
        }

        leaf flowmon-node {
           description
                "The node id where the Flow Monitor will appear e.g. openflow:1 ";
           type inet:uri;
           mandatory true;
        }

        leaf flowmon-mac {
            description
                "Mac address of flowmon";
            type yang:mac-address;
        }
     }
   }

}
