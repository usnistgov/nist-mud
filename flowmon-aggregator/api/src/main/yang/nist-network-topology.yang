module nist-network-topology {
  yang-version 1.1;
  namespace "urn:nist:params:xml:ns:yang:nist-network-topology";
  prefix network-topology;

  import ietf-inet-types {
    prefix inet;
  }
  
  organization
    "NIST Advanced Networking Technologies Division.";

  contact
    "Web: http://www.nist.gov
    email: mranga@nist.gov
    ";
  description
    "Description of the topology of the system. 
     This identifies the npe and cpe devices associated
     with those NPE devices.";

  revision 2017-09-15 {
    description
      "Initial proposed standard.";
    reference
      "RFC XXXX: Manufacturer Usage Description
       Specification";
  }

  grouping links {
      description
          "A list of accounts";
      list link {
         key tag;
         leaf tag  {
            description 
                "Account tag. This is the MPLS / VLAN tag assigned to the packet.
                 when it leaves the CPE switch. Uniquely identifies the CPE.";
            type uint32;
        }

        leaf descriptive-name {
            description 
                "Descriptive name for this link";
            type string;
        }
        

        leaf vnf-switch {
           description
                "VNF switch ID";
            type inet:uri;
        }

        leaf npe-switch {
           description 
                "NPE switch associated with several CPE switches. ";
           type inet:uri;
        }

        leaf cpe-switches-id {
          description 
             "ID of the set of CPE switches associated with this NPE switch.";
          type string;
        }
      }
  }

  container topology {
      description
          "Network topology gives an association between npe switches and 
          sets of CPE switches";
      uses links;
  }

}
